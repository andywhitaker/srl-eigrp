module srl_nokia-eigrp {
  yang-version 1.1;
  namespace "urn:nokia.com:srlinux:eigrp:eigrp";
  prefix srl_nokia-eigrp;

  import srl_nokia-common { prefix srl_nokia-comm; }
  import srl_nokia-network-instance { prefix srl_nokia-netinst; }
  import srl_nokia-routing-policy { prefix srl-rpol; }
  import srl_nokia-extensions { prefix srl_nokia-ext; }
  import srl_nokia-system { prefix srl_nokia-system; }
  import srl_nokia-keychains { prefix srl_nokia-keychains; }

  description "YANG model for EIGRP protocol in Nokia SR Linux";

  grouping eigrp-actions {
    description "EIGRP policy actions";
    container eigrp {
      description "Enter the eigrp context";
      container metric {
        description "Policy actions related to EIGRP route metrics";
        leaf bandwidth {
          type uint32;
          default 100000;
          description "Bandwidth metric in kilobits per second (K1)";
        }
        leaf delay {
          type uint32;
          default 100;
          description "Delay metric in 10-microsecond units (K3)";
        }
        leaf reliability {
          type uint8 {
            range "1..255";
          }
          default 255;
          description "Reliability metric from 1 to 255 (K4)";
        }
        leaf load {
          type uint8 {
            range "1..255";
          }
          default 1;
          description "Effective load metric from 1 to 255 (K2)";
        }
        leaf mtu {
          type uint32 {
            range "576..65535";
          }
          default 1500;
          description "Maximum Transmission Unit in bytes (K5)";
        }
      }
    }
  }

  grouping eigrp-interface-address-family-config {
    list address-family {
      key "name";
      description "Address family configuration for this interface";
      leaf name {
        type enumeration {
          enum ipv4-unicast;
          enum ipv6-unicast;
        }
        description "Address family name";
      }
      leaf admin-state {
        type srl_nokia-comm:admin-state;
        default "enable";
        description "Administrative state of the address family on this interface";
      }
      leaf oper-state {
        config false;
        type srl_nokia-comm:oper-state;
        description "Operational state of the address family on this interface";
      }
      leaf oper-down-reason {
        config false;
        type string;
        description "Reason why the address family is operationally down on this interface";
      }
      leaf ip-address {
        config false;
        type srl_nokia-comm:ip-address;
        description "IP address assigned to the interface for this address family";
      }
      leaf prefix-length {
        config false;
        type uint8;
        description "Prefix length of the interface address for this address family";
      }
      leaf passive {
        type boolean;
        default false;
        description "Suppress sending/receiving EIGRP hellos for this address family";
      }
      leaf hello-interval {
        type uint16 { range "1..65535"; }
        default 5;
        units "seconds";
        description "Hello interval in seconds for this address family";
      }
      leaf hold-time {
        type uint16 { range "1..65535"; }
        default 15;
        units "seconds";
        description "Hold time in seconds for this address family";
      }
      leaf split-horizon {
        type boolean;
        default true;
        description "Enable or disable split-horizon on this interface for this address family";
      }
      leaf next-hop-self {
        type boolean;
        default false;
        description "Advertise this router as next hop on this interface for this address family";
      }
      leaf bandwidth-percent {
        type uint32 { range "1..999999"; }
        default 50;
        units "percent";
        description "Maximum percentage of interface bandwidth that EIGRP may use for this address family";
      }
      container authentication {
        description "Packet authentication configuration for this address family";
        leaf admin-state {
          type srl_nokia-comm:admin-state;
          default "enable";
          description "Administrative state of authentication";
        }
        leaf oper-state {
          config false;
          type srl_nokia-comm:oper-state;
          description "Operational state of authentication";
        }
        leaf mode {
          type enumeration {
            enum none;
            enum md5;
            enum hmac-sha-256;
          }
          default "none";
          description "Authentication mode for EIGRP packets in this address family";
        }
        leaf keychain {
          type leafref {
            path "/srl_nokia-system:system/srl_nokia-keychains:authentication/srl_nokia-keychains:keychain/srl_nokia-keychains:name";
          }
          description "Reference to system authentication keychain (/system/authentication/keychain)";
        }
        leaf authentication-key {
          type string;
          description "Direct plaintext authentication key or password";
        }
      }
      container bfd {
        description "Bidirectional Forwarding Detection (BFD) configuration for this address family";
        leaf admin-state {
          type srl_nokia-comm:admin-state;
          default "disable";
          description "Enable or disable BFD for this address family on this interface";
        }
        leaf oper-state {
          config false;
          type srl_nokia-comm:oper-state;
          description "Operational state of BFD for this address family on this interface";
        }
        leaf desired-minimum-tx-interval {
          type uint32 {
            range "10000..100000000";
          }
          units "microseconds";
          default "1000000";
          description "Desired minimum transmit interval in microseconds";
        }
        leaf required-minimum-receive {
          type uint32 {
            range "10000..100000000";
          }
          units "microseconds";
          default "1000000";
          description "Required minimum receive interval in microseconds";
        }
        leaf detection-multiplier {
          type uint8 {
            range "1..20";
          }
          default "3";
          description "Detection multiplier for BFD session";
        }
      }
      container bfd-state {
        config false;
        description "Operational state of BFD on the interface for this address family";
        leaf session-state {
          type string;
          description "BFD session state (up, down, admin-down, init)";
        }
        leaf remote-address {
          type srl_nokia-comm:ip-address;
          description "Remote peer address monitored by BFD";
        }
      }
      list summary-address {
        key "prefix";
        description "Configure summary address on this interface for this address family";
        leaf prefix {
          type srl_nokia-comm:ip-prefix;
          description "Summary IP prefix to advertise";
        }
        leaf distance {
          type uint8 { range "1..255"; }
          default 5;
          description "Administrative distance for summary discard route";
        }
        leaf oper-state {
          config false;
          type srl_nokia-comm:oper-state;
          description "Operational state of the summary address route";
        }
      }
    }
  }

  grouping eigrp-default-interface-address-family-config {
    list address-family {
      key "name";
      description "Address family configuration for default interface";
      leaf name {
        type enumeration {
          enum ipv4-unicast;
          enum ipv6-unicast;
        }
        description "Address family name";
      }
      leaf admin-state {
        type srl_nokia-comm:admin-state;
        default "enable";
        description "Administrative state of the address family on default interface";
      }
      leaf oper-state {
        config false;
        type srl_nokia-comm:oper-state;
        description "Operational state of the address family on default interface";
      }
      leaf oper-down-reason {
        config false;
        type string;
        description "Reason why the address family is operationally down on default interface";
      }
      leaf passive {
        type boolean;
        default false;
        description "Suppress sending/receiving EIGRP hellos for this address family by default";
      }
      leaf hello-interval {
        type uint16 { range "1..65535"; }
        default 5;
        units "seconds";
        description "Hello interval in seconds for this address family by default";
      }
      leaf hold-time {
        type uint16 { range "1..65535"; }
        default 15;
        units "seconds";
        description "Hold time in seconds for this address family by default";
      }
      leaf split-horizon {
        type boolean;
        default true;
        description "Enable or disable split-horizon by default";
      }
      leaf next-hop-self {
        type boolean;
        default false;
        description "Advertise this router as next hop by default";
      }
      leaf bandwidth-percent {
        type uint32 { range "1..999999"; }
        default 50;
        units "percent";
        description "Maximum percentage of interface bandwidth that EIGRP may use by default";
      }
      container authentication {
        description "Packet authentication configuration for this address family by default";
        leaf admin-state {
          type srl_nokia-comm:admin-state;
          default "enable";
          description "Administrative state of authentication";
        }
        leaf oper-state {
          config false;
          type srl_nokia-comm:oper-state;
          description "Operational state of authentication";
        }
        leaf mode {
          type enumeration {
            enum none;
            enum md5;
            enum hmac-sha-256;
          }
          default "none";
          description "Authentication mode for EIGRP packets in this address family";
        }
        leaf keychain {
          type leafref {
            path "/srl_nokia-system:system/srl_nokia-keychains:authentication/srl_nokia-keychains:keychain/srl_nokia-keychains:name";
          }
          description "Reference to system authentication keychain (/system/authentication/keychain)";
        }
        leaf authentication-key {
          type string;
          description "Direct plaintext authentication key or password";
        }
      }
      container bfd {
        description "Bidirectional Forwarding Detection (BFD) configuration for this address family by default";
        leaf admin-state {
          type srl_nokia-comm:admin-state;
          default "disable";
          description "Enable or disable BFD for this address family by default";
        }
        leaf oper-state {
          config false;
          type srl_nokia-comm:oper-state;
          description "Operational state of BFD for this address family";
        }
        leaf desired-minimum-tx-interval {
          type uint32 {
            range "10000..100000000";
          }
          units "microseconds";
          default "1000000";
          description "Desired minimum transmit interval in microseconds";
        }
        leaf required-minimum-receive {
          type uint32 {
            range "10000..100000000";
          }
          units "microseconds";
          default "1000000";
          description "Required minimum receive interval in microseconds";
        }
        leaf detection-multiplier {
          type uint8 {
            range "1..20";
          }
          default "3";
          description "Detection multiplier for BFD session";
        }
      }
    }
  }

  grouping eigrp-default-interface-config {
    leaf admin-state {
      type srl_nokia-comm:admin-state;
      default "enable";
      description "Administrative state of EIGRP interfaces by default";
    }
    leaf oper-state {
      config false;
      type srl_nokia-comm:oper-state;
      description "Operational state of EIGRP default-interface";
    }
    leaf bandwidth {
      type uint32 { range "1..10000000"; }
      units "kilobits-per-second";
      description "Interface bandwidth in Kbps by default";
    }
    leaf delay {
      type uint32 { range "1..16777215"; }
      units "10-microseconds";
      description "Interface delay in 10-microsecond units by default";
    }
    uses eigrp-default-interface-address-family-config;
  }

  grouping eigrp-interface-config {
    leaf admin-state {
      type srl_nokia-comm:admin-state;
      default "enable";
      description "Administrative state of the EIGRP interface";
    }
    leaf oper-state {
      config false;
      type srl_nokia-comm:oper-state;
      description "Operational state of the EIGRP interface";
    }
    leaf oper-down-reason {
      config false;
      type string;
      description "Reason why the interface is operationally down";
    }
    leaf bandwidth {
      type uint32 { range "1..10000000"; }
      units "kilobits-per-second";
      description "Configured interface bandwidth in Kbps";
    }
    leaf delay {
      type uint32 { range "1..16777215"; }
      units "10-microseconds";
      description "Configured interface delay in 10-microsecond units";
    }
    leaf ip-address {
      config false;
      type srl_nokia-comm:ip-address;
      description "IPv4 address assigned to the interface";
    }
    leaf prefix-length {
      config false;
      type uint8;
      description "IPv4 prefix length of the interface";
    }
    container statistics {
      config false;
      description "Per-interface EIGRP protocol traffic statistics";
      leaf reliable-multicast { type srl_nokia-comm:zero-based-counter64; description "Reliable multicast packets"; }
      leaf unreliable-multicast { type srl_nokia-comm:zero-based-counter64; description "Unreliable multicast packets"; }
      leaf reliable-unicast { type srl_nokia-comm:zero-based-counter64; description "Reliable unicast packets"; }
      leaf unreliable-unicast { type srl_nokia-comm:zero-based-counter64; description "Unreliable unicast packets"; }
      leaf retransmissions { type srl_nokia-comm:zero-based-counter64; description "Retransmitted packets"; }
      leaf cr-packets { type srl_nokia-comm:zero-based-counter64; description "Conditional Receive packets"; }
    }
    uses eigrp-interface-address-family-config;
  }

  grouping eigrp-trace-options {
    container trace-options {
      description
        "Configure EIGRP protocol trace options for diagnostic logging to SR Linux syslog";
      leaf-list trace {
        type enumeration {
          enum adjacencies {
            description "Trace EIGRP neighbor adjacency state transitions and hello negotiations";
          }
          enum packets {
            description "Trace EIGRP packet transmission and reception";
          }
          enum routes {
            description "Trace EIGRP topology table, successor selection, and RIB route updates";
          }
          enum fsm {
            description "Trace DUAL finite state machine transitions and Feasibility Condition evaluations";
          }
          enum graceful-restart {
            description "Trace EIGRP Non-Stop Forwarding (NSF) and Graceful Restart events";
          }
          enum timers {
            description "Trace EIGRP hello, hold, and SIA timer expirations and updates";
          }
          enum events {
            description "Trace general EIGRP protocol and interface events";
          }
          enum all {
            description "Enable all EIGRP trace categories";
          }
        }
        description
          "List of EIGRP trace categories to emit to /var/log/srlinux/buffer/messages";
      }
    }
  }

  grouping eigrp-top {
    container eigrp {
      presence "Configure EIGRP protocol";
      leaf admin-state {
        type srl_nokia-comm:admin-state;
        default "enable";
        description "Administrative state of the EIGRP protocol instance";
      }
      leaf autonomous-system {
        type uint16 {
          range "1..65535";
        }
        mandatory true;
        description "EIGRP Autonomous System Number";
      }
      leaf router-id {
        type srl_nokia-comm:ipv4-address;
        description "EIGRP 32-bit Router ID";
      }
      leaf rib-scale {
        type uint8 {
          range "1..255";
        }
        default 128;
        description "Scale factor for converting 64-bit wide metrics to 32-bit RIB metrics";
      }
      leaf wide-metrics {
        type boolean;
        default true;
        description "Enable RFC 7868 64-bit wide metrics";
      }
      leaf oper-state {
        config false;
        type srl_nokia-comm:oper-state;
        description "Operational state of the EIGRP protocol instance";
      }
      leaf oper-down-reason {
        config false;
        type string;
        description "Reason why the protocol instance is operationally down";
      }
      leaf total-interfaces {
        config false;
        type uint32;
        description "Number of participating interfaces";
      }
      leaf total-neighbors {
        config false;
        type uint32;
        description "Number of active EIGRP neighbors";
      }
      leaf total-routes {
        config false;
        type uint32;
        description "Number of learned EIGRP routes";
      }
      container graceful-restart {
        description "Graceful restart (Non-Stop Forwarding / NSF) configuration";
        leaf admin-state {
          type srl_nokia-comm:admin-state;
          default "enable";
          description "Administrative state of graceful restart";
        }
        leaf restart-time {
          type uint16 {
            range "1..3600";
          }
          default 120;
          units "seconds";
          description "Maximum time allowed to complete restart signaling and resynchronization";
        }
        leaf helper-mode {
          type boolean;
          default true;
          description "Enable graceful restart helper mode to retain forwarding for restarting peers";
        }
        leaf oper-state {
          config false;
          type srl_nokia-comm:oper-state;
          description "Operational state of graceful restart";
        }
      }
      container metrics {
        description "K-values for composite metric calculation";
        leaf bandwidth {
          type uint8;
          default 1;
          description "Bandwidth weight (K1)";
        }
        leaf load {
          type uint8;
          default 0;
          description "Load weight (K2)";
        }
        leaf delay {
          type uint8;
          default 1;
          description "Delay weight (K3)";
        }
        leaf reliability {
          type uint8;
          default 0;
          description "Reliability weight (K4)";
        }
        leaf mtu {
          type uint8;
          default 0;
          description "MTU weight (K5)";
        }
        leaf extended-attributes {
          type uint8;
          default 0;
          description "Extended attributes weight (K6)";
        }
      }
      container timers {
        leaf active-time {
          type uint16;
          default 3;
          units "minutes";
          description "DUAL SIA timer";
        }
      }

      list address-family {
        key "name";
        description "List of address families participating in EIGRP";
        leaf name {
          type enumeration {
            enum ipv4-unicast;
            enum ipv6-unicast;
          }
          description "Address family name";
        }
        leaf admin-state {
          type srl_nokia-comm:admin-state;
          default "enable";
          description "Administrative state of the address family";
        }
        leaf oper-state {
          config false;
          type srl_nokia-comm:oper-state;
          description "Operational state of the address family";
        }
        leaf oper-down-reason {
          config false;
          type string;
          description "Reason why the address family is operationally down";
        }
        leaf export-policy {
          type leafref {
            path "/srl-rpol:routing-policy/srl-rpol:policy/srl-rpol:name";
          }
          description "Export policy for EIGRP route redistribution in this address family";
        }
        leaf import-policy {
          type leafref {
            path "/srl-rpol:routing-policy/srl-rpol:policy/srl-rpol:name";
          }
          description "Import policy for filtering EIGRP routes in this address family";
        }
        leaf variance {
          type uint8 {
            range "1..128";
          }
          default 1;
          description
            "Multiplier for unequal-cost load balancing in this address family.
             Feasible successor routes within the variance window are installed into
             the SR Linux FIB as uniform ECMP multipath due to NDK schema boundaries.";
        }
        leaf maximum-paths {
          type uint8 {
            range "1..64";
          }
          default 4;
          description "Maximum number of parallel equal-cost paths (ECMP) in this address family";
        }
        leaf maximum-hops {
          type uint8 {
            range "1..255";
          }
          default 100;
          description "Maximum hop count limit for EIGRP routes in this address family";
        }
        leaf preference {
          type uint8 {
            range "1..255";
          }
          default 90;
          description "Route table preference (administrative distance) for internal EIGRP routes in this address family";
        }
        leaf external-preference {
          type uint8 {
            range "1..255";
          }
          default 170;
          description "Route table preference (administrative distance) for external EIGRP routes in this address family";
        }
        leaf traffic-share-balanced {
          type boolean;
          default false;
          description "Distribute traffic proportionally to route metrics across unequal-cost paths in this address family";
        }
        leaf auto-summary {
          type boolean;
          default false;
          description "Enable automatic classful network summarization at major network boundaries in this address family";
        }
        container default-metric {
          description "Default seed metric for redistributed routes in this address family";
          leaf bandwidth {
            type uint32 {
              range "1..10000000";
            }
            default 100000;
            units "kilobits-per-second";
            description "Default bandwidth metric in kilobits per second (K1)";
          }
          leaf delay {
            type uint32 {
              range "1..16777215";
            }
            default 100;
            units "10-microseconds";
            description "Default delay metric in 10-microsecond units (K3)";
          }
          leaf reliability {
            type uint8 {
              range "1..255";
            }
            default 255;
            description "Default reliability metric from 1 to 255 (K4)";
          }
          leaf load {
            type uint8 {
              range "1..255";
            }
            default 1;
            description "Default effective load metric from 1 to 255 (K2)";
          }
          leaf mtu {
            type uint32 {
              range "1..65535";
            }
            default 1500;
            units "bytes";
            description "Default Maximum Transmission Unit in bytes (K5)";
          }
        }
        container maximum-prefix {
          description "Maximum number of prefixes accepted in the EIGRP topology table for this address family";
          leaf limit {
            type uint32 {
              range "1..4294967295";
            }
            description "Maximum number of prefixes allowed";
          }
          leaf threshold {
            type uint8 {
              range "1..100";
            }
            default 75;
            units "percent";
            description "Warning threshold percentage";
          }
          leaf warning-only {
            type boolean;
            default false;
            description "Log warning message only when limit is exceeded without dropping routes";
          }
        }
      }

      container default-interface {
        description "Default interface configuration for EIGRP";
        uses eigrp-default-interface-config;
      }

      uses eigrp-trace-options;

      list interface {
        key "interface-name";
        description "List of interfaces participating in EIGRP";
        leaf interface-name {
          type srl_nokia-comm:subinterface-all;
          description "Router logical subinterface name (e.g. ethernet-1/1.0, system0.0)";
        }
        uses eigrp-interface-config;
      }

      list neighbor {
        key "ip-address";
        config false;
        srl_nokia-ext:unordered-state-list "true";
        description "Active EIGRP neighbors";
        leaf ip-address { type srl_nokia-comm:ip-address; }
        leaf address-family { type string; description "Address family of the neighbor (ipv4-unicast or ipv6-unicast)"; }
        leaf interface { type string; }
        leaf state { type string; }
        leaf hold-time { type uint16; }
        leaf uptime { type string; }
        leaf srtt-ms { type uint32; }
        leaf rto-ms { type uint32; }
        leaf bfd-state { type string; description "BFD session operational state"; }
        leaf restart-state { type string; description "Graceful restart status"; }
        leaf auth-mode { type string; description "Authentication mode negotiated/used"; }
        leaf oper-down-reason { type string; description "Reason why neighbor is down or failed to establish"; }
      }
      list static-neighbor {
        key "ip-address";
        description "Statically configured EIGRP neighbors";
        leaf ip-address {
          type srl_nokia-comm:ip-address;
          description "IP address of the static neighbor";
        }
        leaf interface {
          type srl_nokia-comm:subinterface-all;
          mandatory true;
          description "Interface connected to the static neighbor";
        }
        leaf oper-state {
          config false;
          type srl_nokia-comm:oper-state;
          description "Operational state of the static neighbor";
        }
        leaf oper-down-reason {
          config false;
          type string;
          description "Reason why the static neighbor is operationally down";
        }
      }
      container topology {
        config false;
        description "DUAL topology table state";
        leaf total-prefixes {
          type uint32;
          description "Total number of prefixes in the topology table";
        }
        leaf active-prefixes {
          type uint32;
          description "Number of prefixes currently in DUAL Active state";
        }
        list prefix {
          key "prefix";
          srl_nokia-ext:unordered-state-list "true";
          description "DUAL topology table entries";
          leaf prefix { type srl_nokia-comm:ip-prefix; }
          leaf active { type boolean; }
          leaf feasible-distance { type uint32; }
          leaf wide-feasible-distance { type uint64; description "64-bit feasible distance"; }
          leaf successor-count { type uint32; }
          leaf external { type boolean; description "True if redistributed external route"; }
          leaf preference { type uint8; description "Administrative distance (route preference)"; }
          list route {
            key "next-hop";
            srl_nokia-ext:unordered-state-list "true";
            description "Candidate paths and feasible successors for this topology prefix";
            leaf next-hop { type srl_nokia-comm:ip-address; }
            leaf interface { type string; }
            leaf successor { type boolean; }
            leaf feasible-successor { type boolean; }
            leaf distance { type uint32; }
            leaf wide-distance { type uint64; }
            leaf reported-distance { type uint32; }
            leaf wide-reported-distance { type uint64; }
          }
        }
      }
    }
  }

  augment "/srl_nokia-netinst:network-instance/srl_nokia-netinst:protocols" {
    uses eigrp-top;
  }

  augment "/srl-rpol:routing-policy/srl-rpol:policy/srl-rpol:statement/srl-rpol:action" {
    uses eigrp-actions;
  }

  augment "/srl-rpol:routing-policy/srl-rpol:policy/srl-rpol:default-action" {
    uses eigrp-actions;
  }
}
